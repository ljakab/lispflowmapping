module odl-lisp-proto {

    yang-version 1;
    namespace "urn:opendaylight:lfm:lisp-proto";
    prefix "lisp-proto";

    import ietf-inet-types { prefix inet; revision-date 2010-09-24; }
    import ietf-lisp-address-types { prefix lisp-address; revision-date 2015-11-05; }

    organization "LISP Flow Mapping";

    contact
        "David Goldberg <david.goldberg@contextream.com>
        Vina Ermagan <vermagan@cisco.com>";

    description
        "YANG representation of LISP (RFC6830) protocol.";

    revision "2015-11-05" {
        description "Renamed the module to lisp-proto.";
        reference "https://tools.ietf.org/html/rfc6830";
    }

    typedef ipv4-address-binary {
        type binary {
            length "4";
        }
        description
            "The ipv4-address-binary type represents an IPv4 address in binary
             in network byte order.";
    }

    typedef xtr-id {
        type binary {
            length "16";
        }
        description
            "128 bit xTR identifier.";
    }

    typedef site-id {
        type binary {
            length "8";
        }
        description
            "64 bit site identifier.";
    }

    typedef ipv6-address-binary {
        type binary {
            length "16";
        }
        description
            "The ipv6-address-binary type represents an IPv6 address in binary
             in network byte order.";
    }

    typedef ip-address-binary {
        type union {
            type ipv4-address-binary;
            type ipv6-address-binary;
        }
        description
            "The ip-address-binary type represents an IP address in binary
             in network byte order, and is IP version neutral.  The length of
             the byte array implies the IP version.";
    }

    grouping transport-address {
        container transport-address {
            leaf ipAddress {
                type inet:ip-address;
                reference "http://www.iana.org/assignments/safi-namespace/safi-namespace.xhtml";
            }
            leaf port {
                type inet:port-number;
            }
        }
    }

    grouping eid-container {
        container eid {
            uses lisp-address:lisp-address;
        }
    }

    grouping rloc-container {
        container rloc {
            uses lisp-address:lisp-address;
        }
    }

    grouping eid-list {
        list eid-item {
            key "eid-item-id";
            leaf eid-item-id {
                type string;
            }
            uses eid-container;
        }
    }

    grouping LocatorRecords {
        list LocatorRecord {
            key "locator-id";
            leaf locator-id {
                type string;
            }
            leaf priority {
                type uint8;
            }
            leaf weight {
                type uint8;
            }
            leaf multicastPriority {
                type uint8;
            }
            leaf multicastWeight {
                type uint8;
            }
            leaf localLocator {
                type boolean;
            }
            leaf rlocProbed {
                type boolean;
            }
            leaf routed {
                type boolean;
            }

            //locator address
            uses rloc-container;
        }
    }

    grouping mapping-record-metadata {
        leaf xtr-id {
            type xtr-id;
            description
                "128 bit xTR identifier.";
        }
        leaf site-id {
            type site-id;
            description
                "64 bit site identifier.";
        }
        leaf source-rloc {
            type ip-address-binary;
            description
                "The Source IP address used for sending the enclosing control
                 packet in RLOC space.";
        }
        leaf timestamp {
            type int64;
            description
                "Milliseconds since January 1, 1970, 00:00:00 GMT";
        }
        description
            "This is a collection of fields which are not present in the actual
            mapping record defined in RFC 6830, but are used internally in
            OpenDaylight";
    }

    grouping mapping-record-container {
        container mapping-record {
            leaf recordTtl {
                type int32;
            }
            leaf maskLength {
                type uint8;
            }
            leaf mapVersion {
                type int16;
            }
            leaf action {
                type enumeration {
                    enum NoAction;
                    enum NativelyForward;
                    enum SendMapRequest;
                    enum Drop;
                }
            }
            leaf authoritative {
                type boolean;
            }
            // EID prefix
            uses eid-container;

            // locator record list
            uses LocatorRecords;

            // metadata
            uses mapping-record-metadata;
        }
    }

    grouping mapping-record-list {
        list mapping-record-item {
            key "mapping-record-item-id";
            leaf mapping-record-item-id {
                type string;
            }
            uses mapping-record-container;
        }
    }

    grouping xtrSiteId {
        leaf xtrId {
            type xtr-id;
        }
        leaf siteId {
            type site-id;
        }
    }

    grouping MapRegister {
        reference "http://tools.ietf.org/html/rfc6830#section-6.1.6 , http://tools.ietf.org/html/draft-ermagan-lisp-nat-traversal-05#section-4.3";
        leaf proxyMapReply {
            type boolean;
        }
        leaf xtrSiteIdPresent {
            type boolean;
        }
        leaf wantMapNotify {
            type boolean;
        }
        leaf nonce {
            type int64;
        }
        leaf keyId {
            type int16;
        }
        leaf authenticationData {
            type binary;
        }
        leaf mergeEnabled {
            type boolean;
        }
        uses mapping-record-list;
        uses xtrSiteId;
    }

    grouping MapNotify {
        reference "http://tools.ietf.org/html/rfc6830#section-6.1.7 , http://tools.ietf.org/html/draft-ermagan-lisp-nat-traversal-05#section-4.3";
        leaf xtrSiteIdPresent {
            type boolean;
        }
        leaf nonce {
            type int64;
        }
        leaf keyId {
            type int16;
        }
        leaf authenticationData {
            type binary;
        }
        leaf mergeEnabled {
            type boolean;
        }
        uses mapping-record-list;
        uses xtrSiteId;
    }

    grouping MapRequest {
        reference "http://tools.ietf.org/html/rfc6830#section-6.1.2";
        leaf authoritative {
            type boolean;
        }
        leaf mapDataPresent {
            type boolean;
        }
        leaf probe {
            type boolean;
        }
        leaf smr {
            type boolean;
        }
        leaf pitr {
            type boolean;
        }
        leaf smrInvoked {
            type boolean;
        }
        leaf nonce {
            type int64;
        }
        container SourceEid {
            uses eid-container;
        }
        list itrRloc {
            key "itr-rloc-id";
            leaf itr-rloc-id {
                type string;
            }
            uses rloc-container;
        }
        uses eid-list;
        container MapReply {
            uses mapping-record-container;
        }
    }

    grouping MapReply {
        reference "http://tools.ietf.org/html/rfc6830#section-6.1.4";
        leaf probe {
            type boolean;
        }
        leaf nonce {
            type int64;
        }
        leaf echoNonceEnabled {
            type boolean;
        }
        leaf securityEnabled {
            type boolean;
        }
        uses mapping-record-list;
    }

    typedef message-type {
        type enumeration {
            enum reserved {
                value 0;
                description
                    "Reserved";
            }
            enum map-request {
                value 1;
                description
                    "Map-Request control packet";
            }
            enum map-reply {
                value 2;
                description
                    "Map-Reply control packet";
            }
            enum map-register {
                value 3;
                description
                    "Map-Register control packet";
            }
            enum map-notify {
                value 4;
                description
                    "Map-Notify control packet";
            }
            enum map-referral {
                value 6;
                description
                    "Map-Referral control packet";
            }
            enum info {
                value 7;
                description
                    "Info control packet";
            }
            enum encapsulated-control-message {
                value 8;
                description
                    "Encapsulated control packet";
            }
        }
        description
            "Defines the LISP control message types";
        reference "https://tools.ietf.org/html/rfc6830#section-6.1.1";
    }

    grouping MapRegisterMessage {
        container MapRegister {
            uses MapRegister;
        }
        uses transport-address;
    }

    grouping MapRegisterNotification {
        container MapRegister {
            uses MapRegister;
        }
        uses transport-address;
    }

    grouping MapNotifyMessage {
        container MapNotify {
            uses MapNotify;
        }
        uses transport-address;
    }

    grouping MapNotifyNotification {
        container MapNotify {
            uses MapNotify;
        }
        uses transport-address;
    }

    grouping MapRequestMessage {
        container MapRequest {
            uses MapRequest;
        }
        uses transport-address;
    }

    grouping MapRequestNotification {
        container MapRequest {
            uses MapRequest;
        }
        uses transport-address;
    }

    grouping MapReplyMessage {
        container MapReply {
            uses MapReply;
        }
        uses transport-address;
    }

    grouping MapReplyNotification {
        container MapReply {
            uses MapReply;
        }
        uses transport-address;
    }

    notification addMapping {
        uses MapRegisterNotification;
    }

    notification gotMapNotify {
        uses MapNotifyNotification;
    }

    notification requestMapping {
        uses MapRequestNotification;
    }

    notification gotMapReply {
        uses MapReplyNotification;
    }

    notification xtrRequestMapping {
        uses MapRequestNotification;
    }

    notification xtrReplyMapping {
        uses MapReplyNotification;
    }
}
