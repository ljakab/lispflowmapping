module mapping-database {

    yang-version 1;
    namespace "mapping-database";
    prefix "mapping-database";

    import lispflowmapping { prefix lfm; revision-date 2015-03-14; }

    contact "Lorand Jakab <lojakab@cisco.com";

    description
        "An MD-SAL based implementation of a LISP Map-Server database";

    revision "2015-03-14" {
        description "Initial revision.";
    }

    typedef key-ref {
        type instance-identifier;
    }

    typedef mapping-ref {
        type instance-identifier;
    }

    grouping mapping-key {
        uses lfm:LispAddress;
        leaf key-type {
            type uint16;
        }
        leaf key {
            type string;
        }
    }

    rpc add-key {
        input {
            uses mapping-key;
        }
        output {
            leaf key-ref {
                type key-ref;
            }
        }
    }

    rpc get-key {
        input {
            uses lfm:LispAddress;
        }
        output {
            leaf key-ref {
                type key-ref;
            }
            uses mapping-key;
        }
    }

    rpc update-key {
        input {
            container eid {
                uses lfm:LispAddress;
            }
            container key {
                uses mapping-key;
            }
        }
    }

    rpc remove-key {
        input {
            uses lfm:LispAddress;
        }
    }

    rpc update-key-with-ref {
        input {
            leaf key-ref {
                type key-ref;
            }
            uses mapping-key;
        }
    }

    rpc remove-key-with-ref {
        input {
            leaf key-ref {
                type key-ref;
            }
        }
    }

    rpc add-mapping {
        input {
            uses lfm:EidToLocatorRecord;
        }
        output {
            leaf map-ref {
                type mapping-ref;
            }
        }
    }

    rpc get-mapping {
        input {
            uses lfm:LispAddress;
        }
        output {
            leaf map-ref {
                type mapping-ref;
            }
            uses lfm:EidToLocatorRecord;
        }
    }

    rpc update-mapping {
        input {
            container eid {
                uses lfm:LispAddress;
            }
            container mapping {
                uses lfm:EidToLocatorRecord;
            }
        }
    }

    rpc remove-mapping {
        input {
            uses lfm:LispAddress;
        }
    }

    rpc update-mapping-with-ref {
        input {
            leaf map-ref {
                type mapping-ref;
            }
            uses lfm:EidToLocatorRecord;
        }
    }

    rpc remove-mapping-with-ref {
        input {
            leaf map-ref {
                type mapping-ref;
            }
        }
    }
}
